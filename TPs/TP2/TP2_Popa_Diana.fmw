FME workspace TP2_Popa_Diana.fmw

Parameters:
- DestDataset_POSTGIS =
- DestDataset_POSTGIS_10 =
- DestDataset_POSTGIS_11 =
- DestDataset_POSTGIS_13 =
- DestDataset_POSTGIS_8 =
- DestDataset_POSTGIS_9 =
- DestDataset_POSTGIS_RASTER =
- SourceDataset_LAS =
- SourceDataset_LAS_6 =
- SourceDataset_PNGRASTER =
- SourceDataset_SHAPEFILE_11 =
- SourceDataset_SHAPEFILE_13 =
- SourceDataset_SHAPEFILE_7 =
- SourceDataset_SHAPEFILE_8 =
- SourceDataset_SHAPEFILE_9 =

Readers:
- SHAPEFILE_1: SHAPEFILE from $(SourceDataset_SHAPEFILE_11)
- SHAPEFILE_2: SHAPEFILE from $(SourceDataset_SHAPEFILE_9)
- SHAPEFILE_3: SHAPEFILE from $(SourceDataset_SHAPEFILE_8)
- SHAPEFILE_4: SHAPEFILE from $(SourceDataset_SHAPEFILE_13)
- LAS_1: LAS from $(SourceDataset_LAS)
- LAS_2: LAS from $(SourceDataset_LAS_6)
- PNGRASTER_1: PNGRASTER from $(SourceDataset_PNGRASTER)
- SHAPEFILE_5: SHAPEFILE from $(SourceDataset_SHAPEFILE_7)

Writers:
- POSTGIS_1: POSTGIS to $(DestDataset_POSTGIS) in EPSG:3857
- POSTGIS_2: POSTGIS to $(DestDataset_POSTGIS_9)
- POSTGIS_3: POSTGIS to $(DestDataset_POSTGIS_13)
- POSTGIS_4: POSTGIS to $(DestDataset_POSTGIS_11)
- POSTGIS_5: POSTGIS to $(DestDataset_POSTGIS_8)
- POSTGIS_6: POSTGIS to $(DestDataset_POSTGIS_10)
- POSTGIS_RASTER_1: POSTGIS_RASTER to $(DestDataset_POSTGIS_RASTER)

batiments_color (writer POSTGIS_5)
    attributes: _output_color varchar(200), color_rgb varchar(200), g_type varchar(15), g_longitud varchar(50), g_latitude varchar(50), g_elevatio varchar(50), id_uef varchar(80), etage_hors int8, annee_construction int8, utilisation varchar(156), no_arrondissement varchar(80)
batiments_3d_color (writer POSTGIS_2)
    attributes: moyenne_z varchar(200), z_accumulation{}__z varchar(200), z_accumulation{}_normal_z text, z_accumulation{}__part_number numeric(20,0), color_rgb varchar(200), g_type varchar(15), g_longitud varchar(50), g_latitude varchar(50), g_elevatio varchar(50), id_uef varchar(80), etage_hors int8, annee_construction int8, utilisation varchar(156), no_arrondissement varchar(80), _overlaps int8, _sum float8, z_accumulation{}_point_source_id text, z_accumulation{}__geometry text, _output_color varchar(200)
lidar_zone (writer POSTGIS_6)
    attributes: _x varchar(200), _x_scale float8, _x_offset float8, _x_encoding varchar(200), _x_type varchar(200), _x_min float8, _x_max float8, _y varchar(200), _y_scale float8, _y_offset float8, _y_encoding varchar(200), _y_type varchar(200), _y_min float8, _y_max float8, _z varchar(200), _z_scale float8, _z_offset float8, _z_encoding varchar(200), _z_type varchar(200), _z_min float8, _z_max float8, _num_points int8, normal_z text, point_source_id text, _part_number numeric(20,0), _geometry text
ac_sim (writer POSTGIS_3)
    attributes: creation_date varchar(80), crimes_categorie varchar(80), crimes_pdq float8, sim_incident_t varchar(80), sim_description varchar(80), sim_caserne int8, sim_nombre_uni float8, nom_arrondissement varchar(80), no_caserne int4, x float8, y float8, _geometry text, _h3index numeric(20,0), point_count int8
casernes_h3 (writer POSTGIS_4)
    attributes: creation_date varchar(80), crimes_categorie varchar(80), crimes_pdq float8, sim_incident_t varchar(80), sim_description varchar(80), sim_caserne int8, sim_nombre_uni float8, nom_arrondissement varchar(80), no_caserne int4, _x float8, _y float8, _geometry text, _h3index numeric(20,0), point_count int8

Bookmark: Actes criminels et interventions SIM - Reprojection (3857), reconfiguration des attributs, jointure des deux tables
actes-criminels (reader SHAPEFILE_2)
    attributes: CATEGORIE varchar(80), DATE varchar(80), QUART varchar(80), PDQ double, X double, Y double, LONGITUDE double, LATITUDE double
    -> Reprojector_3
Reprojector_3
    DEST = EPSG:3857
    INTERPOLATION_TYPE_NAME = Nearest Neighbor
    RASTER_CELL_SIZE = Preserve Cells
    RASTER_TOLERANCE = 0.0
    REPROJECTED -> Configuration_latitude_ac
Configuration_latitude_ac: SubstringExtractor
    END = 4
    RESULT_ATTR = Latitude_ac
    SRC_STRING = @Value(LATITUDE)
    START = 0
    -> Configuration_longitude_ac
Configuration_longitude_ac: SubstringExtractor
    END = 5
    RESULT_ATTR = Longitude_ac
    SRC_STRING = @Value(LONGITUDE)
    START = 0
    -> FeatureMerger [REQUESTOR]
interventions-sim (reader SHAPEFILE_1)
    attributes: INCIDENT_N number(18,0), CREATION_D varchar(80), INCIDENT_T varchar(80), DESCRIPTIO varchar(80), CASERNE number(18,0), NOM_VILLE varchar(80), NOM_ARROND varchar(80), DIVISION number(18,0), NOMBRE_UNI double, MTM8_X double, MTM8_Y double, LONGITUDE double, LATITUDE double
    -> Reprojector_4
Reprojector_4
    DEST = EPSG:3857
    INTERPOLATION_TYPE_NAME = Nearest Neighbor
    RASTER_CELL_SIZE = Preserve Cells
    RASTER_TOLERANCE = 0.0
    REPROJECTED -> Suppression_Heure
Note: Contrairement aux crimes, l'attribut (SIM) comportant la date de l'événement incluait également l'heure. Afin de pouvoir le joindre au document "Actes criminels", j'ai conservé la date seulement. / - Nouveau champ : "Date"
Suppression_Heure: SubstringExtractor
    END = 9
    RESULT_ATTR = Date
    SRC_STRING = @Value(CREATION_D)
    START = 0
    -> Configuration_latitude_SIM
Note: Reconfiguration de la précision des latitudes et longitudes à deux chiffres après la virgule. Considérant que la localisation des points est approximative afin de conserver la confidentialité des événements, il semblait logique que des points (crimes et interventions) à proximité ayant la même date soient considérés comme le même événement. Cette étape a été appliquée aux crimes et interventions SIM afin de les joindre.
Configuration_latitude_SIM: SubstringExtractor
    END = 4
    RESULT_ATTR = Latitude_SIM
    SRC_STRING = @Value(LATITUDE)
    START = 0
    -> Configuration_longitude_SIM
Configuration_longitude_SIM: SubstringExtractor
    END = 5
    RESULT_ATTR = Longitude_SIM
    SRC_STRING = @Value(LONGITUDE)
    START = 0
    -> FeatureMerger [SUPPLIER]
Note: Jointure des deux tables en fonction des dates et coordonnées X,Y qui sont les mêmes. Il n'y a pas de dédoublement de points car la géométrie a été fusionnée également.
FeatureMerger
    ATTR_ACCUM_MODE = Merge Supplier
    ATTR_CONFLICT_RES = Use Requestor
    IGNORE_NULLS = No
    JOIN_KEYS = @Value(DATE) @Value(Date) AUTO @Value(Latitude_ac) @Value(Latitude_SIM) AUTO @Value(Longitude_ac) @Value(Longitude_SIM) AUTO
    MERGE_TYPE = Attributes and Geometry
    PROCESS_DUPS = NO
    REJECT_NULL_MISSING_KEYS = No
    SUPPLIERS_FIRST = No
    MERGED -> AttributeManager_2
    <REJECTED> -> Logger_2
AttributeManager_2
    ATTR_TABLE:
      RENAME_SET_VALUE CREATION_D > creation_d
      RENAME_SET_VALUE CATEGORIE > crimes_categorie
      REMOVE DATE
      REMOVE QUART
      RENAME_SET_VALUE PDQ > crimes_pdq
      REMOVE X
      REMOVE Y
      REMOVE INCIDENT_N
      RENAME_SET_VALUE INCIDENT_T > sim_incident_t
      RENAME_SET_VALUE DESCRIPTIO > sim_description
      RENAME_SET_VALUE CASERNE > sim_caserne
      REMOVE NOM_VILLE
      REMOVE DIVISION
      RENAME_SET_VALUE NOMBRE_UNI > sim_nombre_uni
      REMOVE MTM8_X
      REMOVE MTM8_Y
      REMOVE Date
      REMOVE Latitude_SIM
      REMOVE Longitude_SIM
      RENAME_SET_VALUE NOM_ARROND > nom_arrondissement
      RENAME_SET_VALUE LONGITUDE > longitude
      RENAME_SET_VALUE LATITUDE > latitude
    USER_EXPOSED_ATTRIBUTES = Latitude,Longitude
    -> GeometryValidator
Logger_2
    LOG_FEATURE = LOG_ONLY
    MAXCOORDS = 20
    MAXFEATS = 20
    MESSAGE = Feature is:
    SEVERITY = INFO

Bookmark: Tendances obtenues et les territoires des casernes - Indexation hexagonale (H3), Jointure spatiale
Note: Validation de la géométrie afin d'assurer le bon fonctionnement de la jointure spatiale
GeometryValidator
    ISSUE_ATTR_NAME = _issues
    PRESETS = Basic Integrity
    REPAIR = Yes
    RULES = NAN_REMOVAL PROCESS_MEASURE]NO]FME_CONTROLLER_QUERY_FILE]transformers/dependencies/geometryvalidator8/NAN_REMOVAL.fme]FME_CONTROLLER_CHOICE]NAN_REMOVAL NULL_REMOVAL FME_CONTROLLER_QUERY_FILE]transformers/dependencies/geometryvalidator8/NULL_REMOVAL.fme]FME_CONTROLLER_CHOICE]NULL_REMOVAL TYPE_REPAIR CONNECT_Z_MODE]FIRST_WINS]ARC_ENDPOINT_TOLERANCE_MODE]Auto]ARC_ENDPOINT_TOLERANCE]<Unused>]FME_CONTROLLER_QUERY_FILE]transformers/dependencies/geometryvalidator8/TYPE_REPAIR.fme]FME_CONTROLLER_CHOICE]TYPE_REPAIR
    SUMMARY = Detailed
    PASSED -> PointOnAreaOverlayer [POINT]
    <REJECTED> -> GeometryValidator__Rejected_
GeometryValidator__Rejected_: Logger
    LOG_FEATURE = LOG_ONLY
    MAXCOORDS = 20
    MAXFEATS = 20
    MESSAGE = Feature is:
    SEVERITY = INFO
territoires-administratifs-casernes (reader SHAPEFILE_3)
    attributes: NOM_CAS_AD varchar(80), NO_CAS_ADM long, OBJECTID long
    -> Reprojector_6
Note: Reprojection à EPSG:4326 (lat, long) afin que l'indexation hexagonale fonctionne.
Reprojector_6
    DEST = EPSG:4326
    INTERPOLATION_TYPE_NAME = Nearest Neighbor
    RASTER_CELL_SIZE = Preserve Cells
    RASTER_TOLERANCE = 0.0
    REPROJECTED -> CoordinateExtractor
CoordinateExtractor
    IND = 0
    MODE = Specify Coordinate
    X_ATTR = _x
    Y_ATTR = _y
    -> GeometryExtractor
    <REJECTED> -> Logger_14
GeometryExtractor
    ATTR = _geometry
    KIND_LONG = FME Binary
    REMOVE_GEOMETRY = No
    -> GeometryValidator_2
    <REJECTED> -> Logger_17
GeometryValidator_2
    ISSUE_ATTR_NAME = _issues
    PRESETS = Basic Integrity
    REPAIR = Yes
    RULES = NAN_REMOVAL PROCESS_MEASURE]NO]FME_CONTROLLER_QUERY_FILE]transformers/dependencies/geometryvalidator8/NAN_REMOVAL.fme]FME_CONTROLLER_CHOICE]NAN_REMOVAL NULL_REMOVAL FME_CONTROLLER_QUERY_FILE]transformers/dependencies/geometryvalidator8/NULL_REMOVAL.fme]FME_CONTROLLER_CHOICE]NULL_REMOVAL TYPE_REPAIR CONNECT_Z_MODE]FIRST_WINS]ARC_ENDPOINT_TOLERANCE_MODE]Auto]ARC_ENDPOINT_TOLERANCE]<Unused>]FME_CONTROLLER_QUERY_FILE]transformers/dependencies/geometryvalidator8/TYPE_REPAIR.fme]FME_CONTROLLER_CHOICE]TYPE_REPAIR
    SUMMARY = Detailed
    PASSED -> H3HexagonalIndexer
    <REJECTED> -> Logger_18
H3HexagonalIndexer
    INDEX_OPERATION = Filling Indexes
    -> Reprojector_7
    <REJECTED> -> Logger_4
Note: Reprojection à EPSG: 3857 suite à l'indexation hexagonale.
Reprojector_7
    DEST = EPSG:3857
    INTERPOLATION_TYPE_NAME = Nearest Neighbor
    RASTER_CELL_SIZE = Preserve Cells
    RASTER_TOLERANCE = 0.0
    SOURCE = EPSG:4326
    REPROJECTED -> PointOnAreaOverlayer [AREA]
Note: Jointure spatiale du résultat (tendances entres crimes et interventions SIM) et les territoires administratifs des casernes.
PointOnAreaOverlayer
    ATTR_ACCUM_MODE = Merge Incoming
    ATTR_CONFLICT_RES = Use Incoming
    DEAGGREGATE_INPUT = Yes
    OV_ATTR = point_count
    POLYS_FIRST = NO
    POINT -> AttributeManager_4
    AREA -> AttributeManager_3
    <REJECTED> -> Logger_3
Note: Nettoyage
AttributeManager_4
    ATTR_TABLE:
      RENAME_SET_VALUE creation_d > creation_date
      REMOVE Latitude
      REMOVE Longitude
      REMOVE longitude
      REMOVE latitude
      REMOVE Latitude_ac
      REMOVE Longitude_ac
      REMOVE NOM_CAS_AD
      RENAME_SET_VALUE NO_CAS_ADM > no_caserne
      REMOVE OBJECTID
      RENAME_SET_VALUE _x > x
      RENAME_SET_VALUE _y > y
    -> NullAttributeMapper
Note: Identification des valeurs nulles
NullAttributeMapper
    ATTRCHOICE = All Attributes
    NULL_TREATMENT = Null
    OTHER_VALUE = :
    SOURCE_ATTR_VAL = Null
    -> ac_sim (writer POSTGIS_3)
AttributeManager_3
    ATTR_TABLE:
      RENAME_SET_VALUE creation_d > creation_date
      REMOVE Latitude
      REMOVE Longitude
      REMOVE longitude
      REMOVE latitude
      REMOVE Latitude_ac
      REMOVE Longitude_ac
      REMOVE NOM_CAS_AD
      RENAME_SET_VALUE NO_CAS_ADM > no_caserne
      REMOVE OBJECTID
    -> casernes_h3 (writer POSTGIS_4)
Logger_3
    LOG_FEATURE = LOG_ONLY
    MAXCOORDS = 20
    MAXFEATS = 20
    MESSAGE = Feature is:
    SEVERITY = INFO
Logger_4
    LOG_FEATURE = LOG_ONLY
    MAXCOORDS = 20
    MAXFEATS = 20
    MESSAGE = Feature is:
    SEVERITY = INFO
Logger_18
    LOG_FEATURE = LOG_ONLY
    MAXCOORDS = 20
    MAXFEATS = 20
    MESSAGE = Feature is:
    SEVERITY = INFO
Logger_17
    LOG_FEATURE = LOG_ONLY
    MAXCOORDS = 20
    MAXFEATS = 20
    MESSAGE = Feature is:
    SEVERITY = INFO
Logger_14
    LOG_FEATURE = LOG_ONLY
    MAXCOORDS = 20
    MAXFEATS = 20
    MESSAGE = Feature is:
    SEVERITY = INFO

Bookmark: Extraction des couleurs du Raster
PNGRASTER (reader PNGRASTER_1)
    attributes: datatype char(255)
    -> RasterBandPropertyExtractor
    -> Reprojector_2
RasterBandPropertyExtractor
    -> ListExploder
Note: Bande alpha n'apparait pas dans le raster alors il n'est pas nécessaire de l'éliminer.
ListExploder
    ATTR_ACCUM_MODE = Merge List Attributes
    ATTR_CONFLICT_RES = Use List Attribute Values
    INDEX_ATTR = _element_index
    LIST_ATTR = _band{}
Reprojector_2
    DEST = EPSG:3857
    INTERPOLATION_TYPE_NAME = Nearest Neighbor
    RASTER_CELL_SIZE = Preserve Cells
    RASTER_TOLERANCE = 0.0
    REPROJECTED -> RasterPropertyExtractor
    REPROJECTED -> RasterResampler
RasterPropertyExtractor
    <REJECTED> -> Logger_7
Note: Pour changer la résolution (RasterResampler)
Logger_7
    LOG_FEATURE = LOG_ONLY
    MAXCOORDS = 20
    MAXFEATS = 20
    MESSAGE = Feature is:
    SEVERITY = INFO
Note: Reéchantillonnage (5m)
RasterResampler
    COLUMNS = 263
    INTERPOLATION_TYPE_NAME = Nearest Neighbor
    ROWCOL_OR_CELLSIZE = RowsColumns
    ROWS = 295
    RESAMPLED -> RasterCellCoercer
    RESAMPLED -> montreal5m (writer POSTGIS_RASTER_1)
    <REJECTED> -> Logger_8
RasterCellCoercer
    CELL_GEOMETRY = Points
    EXTRACT_BAND_VALUES_AS = Attributes
    EXTRACT_NODATA = Yes
    PRESERVE_ATTRIBUTES = Yes
    -> AttributeCreator_2
    <REJECTED> -> Logger_5
AttributeCreator_2
    ATTR_TABLE = SET_TO color_rgb = @Evaluate(@Value(_band{0}.value)/255),@Evaluate(@Value(_band{1}.value)/255),@Evaluate(@Value(_band{2}.value)/255)
    -> ColorConverter
Note: Conversion des couleurs FME en RGB
ColorConverter
    InputAttribute = color_rgb
    InputModel = FME
    OutputModel = RGB
    -> FeatureColorSetter
FeatureColorSetter
    FILL_COLOR = @Value(_output_color)
    MODE = Fixed
    COLORED -> PointOnAreaOverlayer_3 [POINT]
    <REJECTED> -> Logger_9
Logger_9
    LOG_FEATURE = LOG_ONLY
    MAXCOORDS = 20
    MAXFEATS = 20
    MESSAGE = Feature is:
    SEVERITY = INFO
Logger_5
    LOG_FEATURE = LOG_ONLY
    MAXCOORDS = 20
    MAXFEATS = 20
    MESSAGE = Feature is:
    SEVERITY = INFO
Logger_8
    LOG_FEATURE = LOG_ONLY
    MAXCOORDS = 20
    MAXFEATS = 20
    MESSAGE = Feature is:
    SEVERITY = INFO
montreal5m (writer POSTGIS_RASTER_1)
    attributes: datatype varchar(255)

Bookmark: Bâtiments (Geoindex), Unités d'évaluation foncière - Reprojection (3857), jointure spatiale, indexation hexagonale (H3)
dmti_building_2021_p_point (reader SHAPEFILE_5)
    attributes: g_objectid varchar(50), g_uid varchar(36), g_name varchar(70), g_address varchar(45), g_municipa varchar(60), g_prov varchar(2), g_post_cod varchar(7), g_phone varchar(15), g_fax varchar(11), g_toll_fre varchar(15), g_type varchar(15), g_longitud varchar(50), g_latitude varchar(50), g_elevatio varchar(50), g_accuracy varchar(50), g_acq_tech varchar(50), g_dat_acqu varchar(50), g_dat_char varchar(50)
    -> Reprojector
Reprojector
    DEST = EPSG:3857
    INTERPOLATION_TYPE_NAME = Nearest Neighbor
    RASTER_CELL_SIZE = Preserve Cells
    RASTER_TOLERANCE = 0.0
    REPROJECTED -> AttributeKeeper
AttributeKeeper
    CREATE_BULK_MODE_FEATURES = NO
    KEEP_ATTRS = g_elevatio,g_latitude,g_longitud,g_type
    -> PointOnAreaOverlayer_2 [POINT]
uniteevaluationfonciere (reader SHAPEFILE_4)
    attributes: ID_UEV varchar(80), CIVIQUE_DE varchar(80), CIVIQUE_FI varchar(80), NOM_RUE varchar(80), SUITE_DEBU varchar(80), MUNICIPALI varchar(80), ETAGE_HORS number(18,0), NOMBRE_LOG number(18,0), ANNEE_CONS number(18,0), CODE_UTILI varchar(80), LETTRE_DEB varchar(80), LETTRE_FIN varchar(80), LIBELLE_UT varchar(156), CATEGORIE_ varchar(80), MATRICULE8 varchar(80), SUPERFICIE number(18,0), SUPERFIC_1 number(18,0), NO_ARROND_ varchar(80)
    -> Reprojector_5
Reprojector_5
    DEST = EPSG:3857
    INTERPOLATION_TYPE_NAME = Nearest Neighbor
    RASTER_CELL_SIZE = Preserve Cells
    RASTER_TOLERANCE = 0.0
    REPROJECTED -> AttributeManager
AttributeManager
    ATTR_TABLE:
      RENAME_SET_VALUE ID_UEV > id_uef
      REMOVE CIVIQUE_DE
      REMOVE CIVIQUE_FI
      REMOVE NOM_RUE
      REMOVE SUITE_DEBU
      REMOVE MUNICIPALI
      RENAME_SET_VALUE ETAGE_HORS > etage_hors
      RENAME_SET_VALUE NOMBRE_LOG > nombre_log
      RENAME_SET_VALUE ANNEE_CONS > annee_construction
      REMOVE CODE_UTILI
      REMOVE LETTRE_DEB
      REMOVE LETTRE_FIN
      RENAME_SET_VALUE LIBELLE_UT > utilisation
      REMOVE CATEGORIE_
      REMOVE MATRICULE8
      REMOVE SUPERFICIE
      REMOVE SUPERFIC_1
      RENAME_SET_VALUE NO_ARROND_ > no_arrondissement
    -> PointOnAreaOverlayer_2 [AREA]
Note: Jointure spatiale afin d'attribuer les valeurs "z" aux polygones de bâtiments. / - À noter que les points ne couvrent pas tous les polygones alors plusieurs bâtiments n'auront pas d'élévation
PointOnAreaOverlayer_2
    ATTR_ACCUM_MODE = Merge Incoming
    ATTR_CONFLICT_RES = Use Original
    DEAGGREGATE_INPUT = Yes
    OV_ATTR = _overlaps
    POLYS_FIRST = NO
    AREA -> PointOnAreaOverlayer_3 [AREA]
    <REJECTED> -> Logger
Logger
    LOG_FEATURE = LOG_ONLY
    MAXCOORDS = 20
    MAXFEATS = 20
    MESSAGE = Feature is:
    SEVERITY = INFO

Bookmark: Attribution couleurs Raster aux bâtiments
PointOnAreaOverlayer_3
    ATTR_ACCUM_MODE = Merge Incoming
    ATTR_CONFLICT_RES = Use Original
    DEAGGREGATE_INPUT = Yes
    OV_ATTR = _overlaps
    POLYS_FIRST = NO
    AREA -> AttributeKeeper_2
    <REJECTED> -> Logger_19
Note: Nettoyage
AttributeKeeper_2
    CREATE_BULK_MODE_FEATURES = NO
    KEEP_ATTRS = annee_construction,color_rgb,etage_hors,fme_fill_color,g_elevatio,g_latitude,g_longitud,g_type,no_arrondissement,utilisation,id_uef,_output_color
    -> PointOnAreaOverlayer_5 [AREA]
    -> batiments_color (writer POSTGIS_5)
Logger_19
    LOG_FEATURE = LOG_ONLY
    MAXCOORDS = 20
    MAXFEATS = 20
    MESSAGE = Feature is:
    SEVERITY = INFO

Bookmark: Simplification et combinaison de deux nuages de points - Secteur limites Montréal-Nord/Ahuntsic
LAS (reader LAS_1)
    -> PointCloudThinner
PointCloudThinner
    INTERVAL = 30
    THINNED -> PointCloudCombiner
    <REJECTED> -> Logger_10
Logger_10
    LOG_FEATURE = LOG_ONLY
    MAXCOORDS = 20
    MAXFEATS = 20
    MESSAGE = Feature is:
    SEVERITY = INFO
LAS (reader LAS_2)
    -> PointCloudThinner_4
Note: Simplification à une intervalle de 30 pour les deux nuages de points.
PointCloudThinner_4
    INTERVAL = 30
    THINNED -> PointCloudCombiner
    <REJECTED> -> Logger_6
Note: Combinaison des nuages de points
PointCloudCombiner
    ACCUM_ATTRS_NAME = Yes
    EXTRACT_RASTER_NODATA_NAME = No
    SPACING = 1.0
    -> EsriReprojector
    <REJECTED> -> Logger_11
EsriReprojector
    DEST = ESRIWKT|WGS_1984_Web_Mercator_Auxiliary_Sphere|PROJCS["WGS_1984_Web_Mercator_Auxiliary_Sphere",GEOGCS["GCS_WGS_1984",DATUM["D_WGS_1984",SPHEROID["WGS_1984",6378137.0,298.257223563]],PRIMEM["Greenwich",0.0],UNIT["Degree",0.0174532925199433]],PROJECTION["Mercator_Auxiliary_Sphere"],PARAMETER["False_Easting",0.0],PARAMETER["False_Northing",0.0],PARAMETER["Central_Meridian",0.0],PARAMETER["Standard_Parallel_1",0.0],PARAMETER["Auxiliary_Sphere_Type",0.0],UNIT["Meter",1.0]]
    GEOTRANSFORMATION_DIRECTION = Forward
    GEOTRANSFORMATION_NAME = NAD_1983_CSRS_To_WGS_1984
    INTERPOLATION_TYPE_NAME = Nearest Neighbor
    RASTER_CELL_SIZE = Preserve Cells
    RASTER_TOLERANCE = 0.0
    SOURCE = ESRIWKT|NAD_1983_CSRS_MTM_8|PROJCS["NAD_1983_CSRS_MTM_8",GEOGCS["GCS_North_American_1983_CSRS",DATUM["D_North_American_1983_CSRS",SPHEROID["GRS_1980",6378137.0,298.257222101]],PRIMEM["Greenwich",0.0],UNIT["Degree",0.0174532925199433]],PROJECTION["Transverse_Mercator"],PARAMETER["False_Easting",304800.0],PARAMETER["False_Northing",0.0],PARAMETER["Central_Meridian",-73.5],PARAMETER["Scale_Factor",0.9999],PARAMETER["Latitude_Of_Origin",0.0],UNIT["Meter",1.0]]
    REPROJECTED -> PointCloudThinner_5
Note: Deuxième simplification à une intervalle de 5
PointCloudThinner_5
    INTERVAL = 5
    THINNED -> PointCloudPropertyExtractor
    <REJECTED> -> Logger_12
Note: Extraction des attributs et valeurs des nuages de points
PointCloudPropertyExtractor
    CALCULATE_EXTENTS_DISPLAY = No
    POINT_COMPONENTS = x EXISTENCE PROPERTIES MINMAX y EXISTENCE PROPERTIES MINMAX z EXISTENCE PROPERTIES MINMAX
    -> PointCloudCoercer
    <REJECTED> -> Logger_13
Note: Conversion des nuages de points en vecteurs (points)
PointCloudCoercer
    ACCUM_ATTRS_NAME = Yes
    CONVERT_TO_DISPLAY = Individual Points
    PART_NUMBER_ATTR_NAME = _part_number
    POINT_COMPONENTS = normal_z point_source_id
    POINT_COMPONENTS_PRESERVE_DISPLAY = Attributes
    COERCED -> GeometryValidator_3
    <REJECTED> -> Logger_15
GeometryValidator_3
    ISSUE_ATTR_NAME = _issues
    PRESETS = Basic Integrity
    REPAIR = Yes
    RULES = NAN_REMOVAL PROCESS_MEASURE]NO]FME_CONTROLLER_QUERY_FILE]transformers/dependencies/geometryvalidator8/NAN_REMOVAL.fme NULL_REMOVAL FME_CONTROLLER_QUERY_FILE]transformers/dependencies/geometryvalidator8/NULL_REMOVAL.fme]FME_CONTROLLER_CHOICE]NULL_REMOVAL TYPE_REPAIR CONNECT_Z_MODE]FIRST_WINS]ARC_ENDPOINT_TOLERANCE_MODE]Auto]ARC_ENDPOINT_TOLERANCE]<Unused>]FME_CONTROLLER_QUERY_FILE]transformers/dependencies/geometryvalidator8/TYPE_REPAIR.fme
    SUMMARY = Detailed
    PASSED -> GeometryExtractor_2
    <REJECTED> -> Logger_20
GeometryExtractor_2
    ATTR = _geometry
    GENERATE_GEOMETRY_IDS = No
    JSON_MAX_DIGITS = 7
    KIND_LONG = Esri JSON
    OGCVERSION = 1.2
    OGC_WKT_PRECISION_DISPLAY = 64-bit
    OGEOSMS_URL_PREFIX = http://maps.google.com/?q=
    PREFER_POLYGON_OVER_SURFACE = No
    REMOVE_GEOMETRY = No
    -> PointOnAreaOverlayer_5 [POINT]
    -> lidar_zone (writer POSTGIS_6)
    <REJECTED> -> Logger_21
Logger_21
    LOG_FEATURE = LOG_ONLY
    MAXCOORDS = 20
    MAXFEATS = 20
    MESSAGE = Feature is:
    SEVERITY = INFO
Logger_20
    LOG_FEATURE = LOG_ONLY
    MAXCOORDS = 20
    MAXFEATS = 20
    MESSAGE = Feature is:
    SEVERITY = INFO
Logger_15
    LOG_FEATURE = LOG_ONLY
    MAXCOORDS = 20
    MAXFEATS = 20
    MESSAGE = Feature is:
    SEVERITY = INFO
Logger_13
    LOG_FEATURE = LOG_ONLY
    MAXCOORDS = 20
    MAXFEATS = 20
    SEVERITY = INFO
Logger_12
    LOG_FEATURE = LOG_ONLY
    MAXCOORDS = 20
    MAXFEATS = 20
    MESSAGE = Feature is:
    SEVERITY = INFO
Logger_11
    LOG_FEATURE = LOG_ONLY
    MAXCOORDS = 20
    MAXFEATS = 20
    MESSAGE = Feature is:
    SEVERITY = INFO
Logger_6
    LOG_FEATURE = LOG_ONLY
    MAXCOORDS = 20
    MAXFEATS = 20
    MESSAGE = Feature is:
    SEVERITY = INFO

Bookmark: Attribution des valeurs "z" aux bâtiments qui intersectent les points LiDAR
Note: Jointure spatiale pour compléter les valeurs "z" à une zone d'intérêt (limite entre arrondissements Ahuntsic et Montréal-Nord)
PointOnAreaOverlayer_5
    CANDIDATE_LIST_ATTRS_TO_INCLUDE_MODE = All Attributes
    CANDIDATE_LIST_NAME = z_accumulation
    DEAGGREGATE_INPUT = Yes
    GROUP_BY = id_uef
    OV_ATTR = _overlaps
    POLYS_FIRST = YES
    AREA -> ListSummer_2
    <REJECTED> -> Logger_16
Note: Calcul des sommes des élévations par polygone
ListSummer_2
    RESULT = _sum
    SRC_LIST = z_accumulation{}._z
    -> AttributeCreator
Note: Calcul de la moyenne Z par bâtiment
AttributeCreator
    ATTR_TABLE = SET_TO moyenne_z = FME_CONDITIONAL:DEFAULT_VALUE'_FME_NO_OP_'BOOL_OP;OR;COMPOSITE_TEST;1;TEST @Value(_overlaps) > 1'@Evaluate(@round(@Value(_sum)/@Value(_overlaps),4))'FME_NUM_CONDITIONS2___
    -> AttributeManager_7
Note: Nettoyage
AttributeManager_7
    ATTR_TABLE:
      REMOVE z_accumulation{}.fme_basename
      REMOVE z_accumulation{}._x
      REMOVE z_accumulation{}._x_scale
      REMOVE z_accumulation{}._x_offset
      REMOVE z_accumulation{}._x_encoding
      REMOVE z_accumulation{}._x_type
      REMOVE z_accumulation{}._x_min
      REMOVE z_accumulation{}._x_max
      REMOVE z_accumulation{}._y
      REMOVE z_accumulation{}._y_scale
      REMOVE z_accumulation{}._y_offset
      REMOVE z_accumulation{}._y_encoding
      REMOVE z_accumulation{}._y_type
      REMOVE z_accumulation{}._y_min
      REMOVE z_accumulation{}._y_max
      REMOVE z_accumulation{}._z_scale
      REMOVE z_accumulation{}._z_offset
      REMOVE z_accumulation{}._z_encoding
      REMOVE z_accumulation{}._z_type
      REMOVE z_accumulation{}._z_min
      REMOVE z_accumulation{}._z_max
      REMOVE z_accumulation{}._num_points
    -> batiments_3d_color (writer POSTGIS_2)
Logger_16
    LOG_FEATURE = LOG_ONLY
    MAXCOORDS = 20
    MAXFEATS = 20
    MESSAGE = Feature is:
    SEVERITY = INFO

FME custom transformer ColorConverter
Converts color values between different formats (FME
 RGB
 Web RGB and CMYK)
Input:
1 attribute containing a color triplet in either FME, RGB, Web RGB or CMYK format, comma-separated
Output:
Attributes _output_color (full color triplet in the required format), _output_red, output_green and _output_blue
Supported color models:
FME color, RGB values in range 0..1
RGB values in range 0..255
Web RGB values, a hexadecimal string of 6 characters containing an RGB triplet with each value in the range 00..FF
CMYK values in range 0..1 and 0..100
Note that due to rounding errors the resulting colors might be a bit off. Especially any conversions between the RGB and CMYK color spaces might yield results that differ from other applications (since the RGB and CMYK color spaces are slightly different)

Parameters:
- InputAttribute =
- InputModel =
- OutputModel =

Input (input)
    -> TestFilter
Note: Select input color model
TestFilter
    DEFAULT_VALUE = <UNFILTERED>
    TEST_LIST = BOOL_OP,OR,COMPOSITE_TEST,<Unused>,TEST_CLAUSE,"TEST $(InputModel) = FME",FME,BOOL_OP,OR,COMPOSITE_TEST,<Unused>,TEST_CLAUSE,"TEST $(InputModel) = RGB",RGB,BOOL_OP,OR,COMPOSITE_TEST,<Unused>,TEST_CLAUSE,"TEST $(InputModel) = Web RGB",Web RGB,BOOL_OP,OR,COMPOSITE_TEST,<Unused>,TEST_CLAUSE,"TEST $(InputModel) = CMYK (0..100)",CMYK (0..100),BOOL_OP,OR,COMPOSITE_TEST,<Unused>,TEST_CLAUSE,"TEST $(InputModel) = CMYK (0..1)",CMYK (0..1)
    FME -> AttributeSplitter
    RGB -> AttributeSplitter_2
    Web RGB -> StringReplacer
    CMYK (0..100) -> AttributeSplitter_5
    CMYK (0..1) -> AttributeSplitter_4
Note: Select output color model
TestFilter_2
    DEFAULT_VALUE = <UNFILTERED>
    TEST_LIST = BOOL_OP,OR,COMPOSITE_TEST,<Unused>,TEST_CLAUSE,"TEST $(OutputModel) = FME",FME,BOOL_OP,OR,COMPOSITE_TEST,<Unused>,TEST_CLAUSE,"TEST $(OutputModel) = RGB",RGB,BOOL_OP,OR,COMPOSITE_TEST,<Unused>,TEST_CLAUSE,"TEST $(OutputModel) = Web RGB",Web RGB,BOOL_OP,OR,COMPOSITE_TEST,<Unused>,TEST_CLAUSE,"TEST $(OutputModel) = CMYK (0..1)",CMYK (0..1),BOOL_OP,OR,COMPOSITE_TEST,<Unused>,TEST_CLAUSE,"TEST $(OutputModel) = CMYK (0..100)",CMYK (0..100)
    FME -> AttributeManager_5
    RGB -> AttributeManager_2
    Web RGB -> AttributeManager_7
    CMYK (0..1) -> AttributeManager_10
    CMYK (0..100) -> AttributeManager_11
Output (output)

Bookmark: FME color triplet
AttributeSplitter
    ATTR_NAME = $(InputAttribute)
    DELIMITER = ,
    DROP_EMPTY_PARTS = No
    LIST_NAME = _list
    TRIM_OPTION = Both
    -> AttributeManager
AttributeManager
    ATTR_TABLE:
      SET_TO _input_red = @Value(_list{0})
      SET_TO _input_green = @Value(_list{1})
      SET_TO _input_blue = @Value(_list{2})
    -> TestFilter_2

Bookmark: RGB color triplet
AttributeSplitter_2
    ATTR_NAME = $(InputAttribute)
    DELIMITER = ,
    DROP_EMPTY_PARTS = No
    LIST_NAME = _list
    TRIM_OPTION = Both
    -> AttributeManager_3
AttributeManager_3
    ATTR_TABLE:
      SET_TO _input_red = @Evaluate(@Value(_list{0})/255)
      SET_TO _input_green = @Evaluate(@Value(_list{1})/255)
      SET_TO _input_blue = @Evaluate(@Value(_list{2})/255)
    -> TestFilter_2

Bookmark: Web RGB (hexadecimal)
StringReplacer
    CASE = NO
    FIND_TEXT = ^#
    NO_MATCH = _FME_NO_OP_
    REGEXP = YES
    SRC_ATTRS = $(InputAttribute)
    -> AttributeSplitter_3
AttributeSplitter_3
    ATTR_NAME = $(InputAttribute)
    DELIMITER = 2s2s2s
    DROP_EMPTY_PARTS = No
    LIST_NAME = _list
    TRIM_OPTION = Both
    -> BaseConverter
BaseConverter
    DBASE = 10
    OBASE = 16
    SRC = _list{0}
    VAL_ATTR = _input_red
    WIDTH = 3
    -> BaseConverter_2
BaseConverter_2
    DBASE = 10
    OBASE = 16
    SRC = _list{1}
    VAL_ATTR = _input_green
    WIDTH = 3
    -> BaseConverter_3
BaseConverter_3
    DBASE = 10
    OBASE = 16
    SRC = _list{2}
    VAL_ATTR = _input_blue
    WIDTH = 3
    -> AttributeManager_4
AttributeManager_4
    ATTR_TABLE:
      SET_TO _input_red = @Evaluate(@Value(_input_red)/255)
      SET_TO _input_green = @Evaluate(@Value(_input_green)/255)
      SET_TO _input_blue = @Evaluate(@Value(_input_blue)/255)
    -> TestFilter_2

Bookmark: CMYK
AttributeSplitter_5
    ATTR_NAME = $(InputAttribute)
    DELIMITER = ,
    DROP_EMPTY_PARTS = No
    LIST_NAME = _list
    TRIM_OPTION = Both
    -> AttributeManager_9
AttributeManager_9
    ATTR_TABLE:
      SET_TO _input_red = @Evaluate((1-(@Value(_list{0})/100))*(1-(@Value(_list{3})/100)))
      SET_TO _input_green = @Evaluate((1-(@Value(_list{1})/100))*(1-(@Value(_list{3})/100)))
      SET_TO _input_blue = @Evaluate((1-(@Value(_list{2})/100))*(1-(@Value(_list{3})/100)))
    -> TestFilter_2
AttributeSplitter_4
    ATTR_NAME = $(InputAttribute)
    DELIMITER = ,
    DROP_EMPTY_PARTS = No
    LIST_NAME = _list
    TRIM_OPTION = Both
    -> AttributeManager_8
AttributeManager_8
    ATTR_TABLE:
      SET_TO _input_red = @Evaluate((1-@Value(_list{0}))*(1-@Value(_list{3})))
      SET_TO _input_green = @Evaluate((1-@Value(_list{1}))*(1-@Value(_list{3})))
      SET_TO _input_blue = @Evaluate((1-@Value(_list{2}))*(1-@Value(_list{3})))
    -> TestFilter_2

Bookmark: FME color triplet
AttributeManager_5
    ATTR_TABLE:
      RENAME_SET_VALUE _input_red > _output_red
      RENAME_SET_VALUE _input_green > _output_green
      RENAME_SET_VALUE _input_blue > _output_blue
      SET_TO _output_color = @Value(_output_red),@Value(_output_green),@Value(_output_blue)
    -> Output (output)

Bookmark: RGB color triplet
AttributeManager_2
    ATTR_TABLE:
      SET_TO _output_red = @Evaluate(@int(@Value(_input_red)*255))
      SET_TO _output_green = @Evaluate(@int(@Value(_input_green)*255))
      SET_TO _output_blue = @Evaluate(@int(@Value(_input_blue)*255))
      SET_TO _output_color = @Value(_output_red),@Value(_output_green),@Value(_output_blue)
    -> Output (output)

Bookmark: Web RGB (hexadecimal
AttributeManager_7
    ATTR_TABLE:
      SET_TO _input_red = @Evaluate(int(@Value(_input_red)*255))
      SET_TO _input_green = @Evaluate(int(@Value(_input_green)*255))
      SET_TO _input_blue = @Evaluate(int(@Value(_input_blue)*255))
    -> BaseConverter_4
    -> AttributeManager_7_Output
BaseConverter_4
    DBASE = 16
    OBASE = 10
    SRC = _input_red
    VAL_ATTR = _output_red
    WIDTH = 2
    -> BaseConverter_5
BaseConverter_5
    DBASE = 16
    OBASE = 10
    SRC = _input_green
    VAL_ATTR = _output_green
    WIDTH = 2
    -> BaseConverter_6
BaseConverter_6
    DBASE = 16
    OBASE = 10
    SRC = _input_blue
    VAL_ATTR = _output_blue
    WIDTH = 2
    -> AttributeManager_6
AttributeManager_6
    ATTR_TABLE = SET_TO _output_color = #@Value(_output_red)@Value(_output_green)@Value(_output_blue)
    -> Output (output)
AttributeManager_7_Output: Inspector

Bookmark: CMYK
AttributeManager_10
    ATTR_TABLE:
      SET_TO _output_key = @Evaluate(1-@max(@Value(_input_red),@Value(_input_green),@Value(_input_blue)))
      SET_TO _output_cyan = @Evaluate((1-@Value(_input_red)-@Value(_output_key))/(1-@Value(_output_key)))
      SET_TO _output_magenta = @Evaluate((1-@Value(_input_green)-@Value(_output_key))/(1-@Value(_output_key)))
      SET_TO _output_yellow = @Evaluate((1-@Value(_input_blue)-@Value(_output_key))/(1-@Value(_output_key)))
    -> AttributeRounder
AttributeManager_11
    ATTR_TABLE:
      SET_TO _output_key = @Evaluate((1-@max(@Value(_input_red),@Value(_input_green),@Value(_input_blue)))*100)
      SET_TO _output_cyan = @Evaluate(((1-@Value(_input_red)-@Value(_output_key))/(1-@Value(_output_key)))*100)
      SET_TO _output_magenta = @Evaluate(((1-@Value(_input_green)-@Value(_output_key))/(1-@Value(_output_key)))*100)
      SET_TO _output_yellow = @Evaluate(((1-@Value(_input_blue)-@Value(_output_key))/(1-@Value(_output_key)))*100)
    -> AttributeRounder
AttributeRounder
    PLACES = 2
    ROUND_TYPE = Nearest
    SRC_ATTRS = _output_cyan _output_key _output_yellow _output_magenta
    -> AttributeManager_12
AttributeManager_12
    ATTR_TABLE = SET_TO _output_color = @Value(_output_cyan),@Value(_output_magenta),@Value(_output_yellow),@Value(_output_key)
    -> Output (output)
